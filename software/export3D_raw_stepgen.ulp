#usage "NoABS.Eagle3D STEP launcher.\n\
Runs eagle2step (exe or python) to produce a single <name>.step (board + components).\n\
No texture rendering is needed for STEP. Reads NOABS_MIN_PRIORITY3D / NOABS_LEAVE_ARTIFACTS\n\
from board attributes; step_components_dir is taken by the Python side from noabs.ini.\n\
Invoked by export3D.ulp; not meant to be run directly."

string win_path(string s)
{
  string result = s;
  int i;
  for (i = 0; result[i]; i++)
    if (result[i] == '/') result[i] = '\\';
  return result;
}

// Read a global board attribute by name; "" if absent.
string get_attr(string nm)
{
  string r = "";
  board(B) B.attributes(A) if (A.name == nm) r = A.value;
  return r;
}

// Integer attribute with default.
int attr_int(string nm, int def)
{
  string v = get_attr(nm);
  if (strlen(v) == 0) return def;
  return strtol(v);
}

void main()
{
  if (!board) { dlgMessageBox("export3D_raw_stepgen: no .brd file is open."); exit(1); }

  // ── Board paths ─────────────────────────────────────────────────────────────
  string board_dir, brd_full, tmp_dir;
  board(B)
  {
    board_dir = filedir(B.name);
    brd_full  = B.name;
    tmp_dir   = board_dir + "NoABS_tmp/";
  }
  string scripts_dir = filedir(argv[0]);

  // ── Settings from board attributes ───────────────────────────────────────────
  int min_pri = attr_int("NOABS_MIN_PRIORITY3D", 0);
  int leave   = attr_int("NOABS_LEAVE_ARTIFACTS", 0);

  // ── Resolve runner: prefer bundled exe, fall back to python + script ──────────
  string sd = scripts_dir;
  int sdlen = strlen(sd);
  if (sdlen > 0 && (sd[sdlen-1] == '/' || sd[sdlen-1] == '\\'))
    sd[sdlen-1] = '\0';
  // onedir puts the exe in a subfolder; onefile/dev keep it flat. Check both, else python.
  string exe_sub  = win_path(sd + "/eagle2step/eagle2step.exe");
  string exe_flat = win_path(sd + "/eagle2step.exe");
  string py_path  = win_path(sd + "/eagle2step.py");

  string runner;
  if (filesize(exe_sub) > 0)
    runner = "\"" + exe_sub + "\"";
  else if (filesize(exe_flat) > 0)
    runner = "\"" + exe_flat + "\"";
  else
    runner = "python \"" + py_path + "\"";

  // NoABS_tmp must exist before the .bat redirects its log there.
  system("cmd.exe /c mkdir \"" + win_path(tmp_dir) + "\" 2>nul");
  string log_path = win_path(tmp_dir + "eagle2step.log");

  // ── Build command line ────────────────────────────────────────────────────────
  string py_cmd, s;
  py_cmd  = runner;
  py_cmd += " \"" + win_path(brd_full) + "\"";
  if (min_pri > 0) { sprintf(s, " --min-priority %d", min_pri); py_cmd += s; }
  if (leave) py_cmd += " --leave-artifacts";
  py_cmd += " > \"" + log_path + "\" 2>&1";

  // ── Run via a .bat (reliable PATH handling); propagate exit code ──────────────
  string bat_path = win_path(tmp_dir + "run_eagle2step.bat");
  output(bat_path, "wt")
  {
    printf("@echo off\r\n");
    printf("%s\r\n", py_cmd);
    printf("exit /b %%errorlevel%%\r\n");
  }
  int ret = system("cmd.exe /c \"" + bat_path + "\"");

  // ── Cleanup: drop NoABS_tmp on success unless artifacts are requested ──────────
  if (ret == 0 && !leave)
    system("cmd.exe /c rmdir /s /q \"" + win_path(tmp_dir) + "\" 2>nul");
  else if (ret != 0)
    dlgMessageBox("STEP generation failed (exit code " + ret + ").\n"
                + "See " + log_path);
}
