#usage "Export board textures and generate 3D GLB model.\n\
Usage:\n\
  RUN export3D_raw.ulp                                  -- interactive (dialog / saved settings)\n\
  RUN export3D_raw.ulp CLEAN                            -- remove NoABS_tmp folder\n\
  RUN export3D_raw.ulp '<dpi>'                          -- CLI: DPI only, other settings from ini\n\
  RUN export3D_raw.ulp '<glb_dir>' '<dpi>'              -- CLI: glb_dir + DPI, min_priority from ini\n\
  RUN export3D_raw.ulp '<glb_dir>' '<dpi>' '<minpri>'   -- CLI: all three explicit\n\
    glb_dir : path to GLB components folder, or empty string '' for no components\n\
    dpi     : export image DPI (e.g. 400)\n\
    minpri  : minimum Priority3d to include (0 = all, default 0)\n\
CLI via eaglecon (exports textures, generates GLB, closes Eagle without saving):\n\
  eaglecon.exe -C \"run export3D_raw.ulp 'C:/libs/glb' '400' '1'; UNDO; QUIT\" board.brd\n\
Note: UNDO reverts ratsnest fill so the board is not marked as modified before QUIT."

string win_path(string s)
{
  string result = s;
  int i;
  for (i = 0; result[i]; i++)
    if (result[i] == '/') result[i] = '\\';
  return result;
}

string read_ini_value(string ini_path, string key)
{
  string lines[];
  int n = fileread(lines, ini_path);
  int klen = strlen(key);
  string result = "";
  int i;
  for (i = 0; i < n; i++)
  {
    if (strsub(lines[i], 0, klen + 1) == key + "=")
    {
      result = strsub(lines[i], klen + 1);
      int rlen = strlen(result);
      if (rlen > 0 && result[rlen-1] == '\n') { result[rlen-1] = '\0'; rlen--; }
      if (rlen > 0 && result[rlen-1] == '\r') { result[rlen-1] = '\0'; }
    }
  }
  return result;
}

void main()
{
  // ── CLEAN режим ──────────────────────────────────────────────────────────────
  if (argc >= 2 && strupr(argv[1]) == "CLEAN")
  {
    if (!board) { dlgMessageBox("Error: no .brd file is open."); exit(1); }
    string bd, tmp;
    board(B) { bd = filedir(B.name); tmp = bd + "NoABS_tmp/"; }
    system("cmd.exe /c rmdir /s /q \"" + win_path(tmp) + "\" 2>nul");
    dlgMessageBox("NoABS_tmp cleaned:\n" + tmp);
    exit(0);
  }

  if (!board) { dlgMessageBox("Error: no .brd file is open."); exit(1); }

  // ── Пути из открытой платы ───────────────────────────────────────────────────
  string board_dir, brd_stem, brd_full, tmp_dir, textures_dir;
  board(B)
  {
    board_dir    = filedir(B.name);
    brd_stem     = filesetext(filename(B.name), "");
    brd_full     = B.name;
    tmp_dir      = board_dir + "NoABS_tmp/";
    textures_dir = tmp_dir + brd_stem + "_textures/";
  }

  // scripts_dir — всегда папка самого ULP
  string scripts_dir = filedir(argv[0]);

  string settings_ini = tmp_dir + "export3d_settings.ini";

  // ── Значения по умолчанию ────────────────────────────────────────────────────
  int    dpi          = 400;
  string glb_dir      = "";
  int    min_priority = 0;

  // ── Определяем режим запуска ─────────────────────────────────────────────────
  //   argc == 1       → интерактивный (ini или диалог)
  //   argc == 2       → CLI: DPI, остальное из ini
  //   argc == 3       → CLI: glb_dir + DPI, min_priority из ini
  //   argc >= 4       → CLI: glb_dir + DPI + min_priority, всё явно

  int cli_mode = (argc >= 2);

  if (argc >= 4)
  {
    glb_dir      = argv[1];
    dpi          = strtol(argv[2]);
    min_priority = strtol(argv[3]);
  }
  else if (argc == 3)
  {
    glb_dir = argv[1];
    dpi     = strtol(argv[2]);
    if (filesize(settings_ini) > 0)
    {
      string mp_str = read_ini_value(settings_ini, "min_priority");
      if (strlen(mp_str) > 0) min_priority = strtol(mp_str);
    }
  }
  else if (argc == 2)
  {
    dpi = strtol(argv[1]);
    if (filesize(settings_ini) > 0)
    {
      string gd = read_ini_value(settings_ini, "glb_dir");
      glb_dir = gd;
      string mp_str = read_ini_value(settings_ini, "min_priority");
      if (strlen(mp_str) > 0) min_priority = strtol(mp_str);
    }
  }
  else
  {
    // Интерактивный режим: сначала загружаем сохранённые настройки
    if (filesize(settings_ini) > 0)
    {
      string dpi_str = read_ini_value(settings_ini, "dpi");
      if (strlen(dpi_str) > 0) dpi = strtol(dpi_str);
      string gd = read_ini_value(settings_ini, "glb_dir");
      glb_dir = gd;
      string mp_str = read_ini_value(settings_ini, "min_priority");
      if (strlen(mp_str) > 0) min_priority = strtol(mp_str);
    }

    // Показываем диалог только при первом запуске (нет ini)
    if (filesize(settings_ini) <= 0)
    {
      system("cmd.exe /c mkdir \"" + win_path(tmp_dir) + "\" 2>nul");

      if (dlgDialog("Export 3D — Initial Setup")
      {
        dlgLabel("Settings will be saved and reused on next run.");
        dlgGroup("Image export")
        {
          dlgHBoxLayout
          {
            dlgLabel("DPI:");
            dlgIntEdit(dpi, 1, 9999);
            dlgStretch(1);
          }
        }
        dlgGroup("Components (optional)")
        {
          dlgHBoxLayout
          {
            dlgLabel("GLB dir:");
            dlgStringEdit(glb_dir);
            dlgPushButton("...") glb_dir = dlgDirectory("Select GLB components directory", glb_dir);
          }
          dlgHBoxLayout
          {
            dlgLabel("Min Priority3d:");
            dlgIntEdit(min_priority, 0, 9999);
            dlgStretch(1);
          }
        }
        dlgHBoxLayout
        {
          dlgPushButton("+OK")     dlgAccept();
          dlgPushButton("-Cancel") dlgReject();
        }
      } != 1)
        exit(0);

      // Сохраняем настройки
      string dpi_save; sprintf(dpi_save, "%d", dpi);
      string mp_save;  sprintf(mp_save,  "%d", min_priority);
      output(settings_ini, "wt")
      {
        printf("dpi=%s\n",          dpi_save);
        printf("glb_dir=%s\n",      glb_dir);
        printf("min_priority=%s\n", mp_save);
      }
    }
  }

  // ── Создаём рабочие папки ─────────────────────────────────────────────────────
  system("cmd.exe /c mkdir \"" + win_path(tmp_dir) + "\" 2>nul");
  system("cmd.exe /c mkdir \"" + win_path(textures_dir) + "\" 2>nul");
  system("cmd.exe /c del /f /q \"" + win_path(textures_dir) + "*.png\"");

  // ── step1.log ─────────────────────────────────────────────────────────────────
  output(win_path(tmp_dir + "step1.log"), "wt")
  {
    printf("board_dir    = %s\n", board_dir);
    printf("brd_stem     = %s\n", brd_stem);
    printf("brd_full     = %s\n", brd_full);
    printf("tmp_dir      = %s\n", tmp_dir);
    printf("textures_dir = %s\n", textures_dir);
    printf("scripts_dir  = %s\n", scripts_dir);
    printf("glb_dir      = %s\n", glb_dir);
    printf("min_priority = %d\n", min_priority);
    printf("cli_mode     = %d\n", cli_mode);
  }

  // ── ini для step2 ─────────────────────────────────────────────────────────────
  string ini_path = tmp_dir + "export3d.ini";
  output(ini_path, "wt")
  {
    printf("brd_full=%s\n",      brd_full);
    printf("tmp_dir=%s\n",       tmp_dir);
    printf("brd_stem=%s\n",      brd_stem);
    printf("glb_dir=%s\n",       glb_dir);
    printf("min_priority=%d\n",  min_priority);
  }

  // ── Eagle-команды: экспорт текстур ───────────────────────────────────────────
  string dpi_str;
  sprintf(dpi_str, "%d", dpi);

  string cmd;
  cmd  = "EDIT .sch;\n";
  cmd += "VARIANT '';\n";
  cmd += "edit .brd;\n";
  cmd += "ratsnest;\n";
  if (EAGLE_VERSION >= 9)
  {
    cmd += "set Option.SignalNamesOnPads 0;\n";
    cmd += "set Option.SignalNamesOnTraces 0;\n";
  }
  cmd += "set Option.ViaLength 0;\n";
  cmd += "set PAD_NAMES OFF;\n";
  cmd += "SET FILL_LAYER 29 1;\n";
  cmd += "SET FILL_LAYER 30 1;\n";

  cmd += "display none;\ndisplay 20;\ndisplay 46;\n";
  cmd += "EXPORT IMAGE '" + textures_dir + "outline.png' MONOCHROME " + dpi_str + ";\n";
  cmd += "display none;\ndisplay 1 17 18;\n";
  cmd += "EXPORT IMAGE '" + textures_dir + "top_copper.png' MONOCHROME " + dpi_str + ";\n";
  cmd += "display none;\ndisplay 21;\n";
  cmd += "EXPORT IMAGE '" + textures_dir + "top_silk.png' MONOCHROME " + dpi_str + ";\n";
  cmd += "display none;\ndisplay 16 17 18;\n";
  cmd += "EXPORT IMAGE '" + textures_dir + "bottom_copper.png' MONOCHROME " + dpi_str + ";\n";
  cmd += "display none;\ndisplay 22;\n";
  cmd += "EXPORT IMAGE '" + textures_dir + "bottom_silk.png' MONOCHROME " + dpi_str + ";\n";
  cmd += "display none;\ndisplay 29;\n";
  cmd += "EXPORT IMAGE '" + textures_dir + "top_mask.png' MONOCHROME " + dpi_str + ";\n";
  cmd += "display none;\ndisplay 30;\n";
  cmd += "EXPORT IMAGE '" + textures_dir + "bottom_mask.png' MONOCHROME " + dpi_str + ";\n";
  cmd += "display none;\ndisplay 17;\n";
  cmd += "EXPORT IMAGE '" + textures_dir + "pads.png' MONOCHROME " + dpi_str + ";\n";

  cmd += "display none;\n";
  if (EAGLE_VERSION >= 9)
  {
    cmd += "set Option.SignalNamesOnPads 1;\n";
    cmd += "set Option.SignalNamesOnTraces 1;\n";
  }
  cmd += "set PAD_NAMES ON;\n";
  cmd += "display 20 17 18 1 21 23 25;\n";

  // ── Запускаем step2 ───────────────────────────────────────────────────────────
  string step2_path = scripts_dir;
  int slen = strlen(step2_path);
  if (slen > 0 && step2_path[slen-1] != '/' && step2_path[slen-1] != '\\')
    step2_path += "/";
  int ci;
  for (ci = 0; step2_path[ci]; ci++)
    if (step2_path[ci] == '\\') step2_path[ci] = '/';
  step2_path += "export3D_raw_step2.ulp";

  string cli_flag; sprintf(cli_flag, "%d", cli_mode);
  cmd += "RUN '" + step2_path + "' '" + ini_path + "' '" + cli_flag + "';\n";


  exit(cmd);
}
