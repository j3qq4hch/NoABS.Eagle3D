// pcb_realistic.ulp
// Экспортирует реалистичную цветную текстуру верхней стороны PCB.
// Запускать из Board Editor: RUN pcb_realistic.ulp

string win_path(string s) {
    string result;
    int i;
    result = s;
    for (i = 0; result[i]; i++)
        if (result[i] == '/') result[i] = '\\';
    return result;
}

string read_ini(string path, string key) {
    string lines[];
    string result;
    int n, i, klen, rlen;
    n = fileread(lines, path);
    klen = strlen(key);
    result = "";
    for (i = 0; i < n; i++) {
        if (strsub(lines[i], 0, klen + 1) == key + "=") {
            result = strsub(lines[i], klen + 1);
            rlen = strlen(result);
            if (rlen > 0 && result[rlen-1] == '\n') { result[rlen-1] = '\0'; rlen--; }
            if (rlen > 0 && result[rlen-1] == '\r') { result[rlen-1] = '\0'; }
        }
    }
    return result;
}

void main() {
    string board_dir, brd_stem, tmp_dir, tex_dir, ini_path;
    string cmd, s, dpi_s, v;
    int mask_choice, finish_choice, silk_choice, dpi, ok, i;
    int saved_pal[];
    int saved_col[];
    int p, aa, rr, gg, bb;
    int r_mask, g_mask, b_mask;
    int r_cu, g_cu, b_cu;
    int r_fin, g_fin, b_fin;
    int r_silk, g_silk, b_silk;

    if (!board) { dlgMessageBox("Error: no .brd file is open."); exit(1); }

    board(B) {
        board_dir = filedir(B.name);
        brd_stem  = filesetext(filename(B.name), "");
        tmp_dir   = board_dir + "NoABS_tmp/";
        tex_dir   = tmp_dir + brd_stem + "_textures/";
    }
    ini_path = tmp_dir + "pcb_realistic.ini";
    system("cmd.exe /c mkdir \"" + win_path(tmp_dir) + "\" 2>nul");
    system("cmd.exe /c mkdir \"" + win_path(tex_dir) + "\" 2>nul");

    // ── Пресеты паяльной маски ─────────────────────────────────────────────
    // packed (r<<16)|(g<<8)|b
    string mask_names[];
    int mask_color[];
    int copper_color[];
    mask_names[0] = "Зелёный";    mask_color[0] = 0x1A7C0F; copper_color[0] = 0x298D29;
    mask_names[1] = "Синий";      mask_color[1] = 0x1A18BF; copper_color[1] = 0x2828D8;
    mask_names[2] = "Красный";    mask_color[2] = 0x9F180F; copper_color[2] = 0xAE2929;
    mask_names[3] = "Чёрный";     mask_color[3] = 0x1A180F; copper_color[3] = 0x292929;
    mask_names[4] = "Фиолетовый"; mask_color[4] = 0x9F1873; copper_color[4] = 0xAE298D;
    mask_names[5] = "Белый";      mask_color[5] = 0xE2E0D7; copper_color[5] = 0xF1F1F1;

    // ── Пресеты покрытия падов ─────────────────────────────────────────────
    string finish_names[];
    int finish_color[];
    finish_names[0] = "ENIG (золото)"; finish_color[0] = 0xD4AF37;
    finish_names[1] = "HASL (олово)";  finish_color[1] = 0xC0C0C0;

    // ── Пресеты шелкографии ────────────────────────────────────────────────
    string silk_names[];
    int silk_color[];
    silk_names[0] = "Белая";  silk_color[0] = 0xFEFEFE;
    silk_names[1] = "Чёрная"; silk_color[1] = 0x010101;

    // ── Значения по умолчанию ──────────────────────────────────────────────
    mask_choice   = 0;
    finish_choice = 0;
    silk_choice   = 0;
    dpi           = 400;

    // ── Загрузка сохранённых настроек ─────────────────────────────────────
    if (filesize(ini_path) > 0) {
        v = read_ini(ini_path, "mask_choice");   if (strlen(v)) mask_choice   = strtol(v);
        v = read_ini(ini_path, "finish_choice"); if (strlen(v)) finish_choice = strtol(v);
        v = read_ini(ini_path, "silk_choice");   if (strlen(v)) silk_choice   = strtol(v);
        v = read_ini(ini_path, "dpi");           if (strlen(v)) dpi           = strtol(v);
    }

    // ── Диалог ────────────────────────────────────────────────────────────
    ok = dlgDialog("PCB Texture Export") {
        dlgGroup("Паяльная маска") {
            dlgComboBox(mask_names, mask_choice);
        }
        dlgGroup("Покрытие падов") {
            dlgComboBox(finish_names, finish_choice);
        }
        dlgGroup("Шелкография") {
            dlgComboBox(silk_names, silk_choice);
        }
        dlgHBoxLayout {
            dlgLabel("DPI:"); dlgIntEdit(dpi, 72, 1200);
            dlgStretch(1);
        }
        dlgHBoxLayout {
            dlgPushButton("+OK")     { dlgAccept(1); }
            dlgPushButton("-Отмена") { dlgReject(0); }
        }
    };
    if (!ok) exit(0);

    // ── Сохраняем настройки ────────────────────────────────────────────────
    output(ini_path, "wt") {
        printf("mask_choice=%d\n",   mask_choice);
        printf("finish_choice=%d\n", finish_choice);
        printf("silk_choice=%d\n",   silk_choice);
        printf("dpi=%d\n",           dpi);
    }

    // ── Извлекаем RGB из выбранных пресетов ───────────────────────────────
    r_mask = (mask_color[mask_choice]     >> 16) & 0xFF;
    g_mask = (mask_color[mask_choice]     >>  8) & 0xFF;
    b_mask =  mask_color[mask_choice]            & 0xFF;

    r_cu   = (copper_color[mask_choice]   >> 16) & 0xFF;
    g_cu   = (copper_color[mask_choice]   >>  8) & 0xFF;
    b_cu   =  copper_color[mask_choice]          & 0xFF;

    r_fin  = (finish_color[finish_choice] >> 16) & 0xFF;
    g_fin  = (finish_color[finish_choice] >>  8) & 0xFF;
    b_fin  =  finish_color[finish_choice]        & 0xFF;

    r_silk = (silk_color[silk_choice]     >> 16) & 0xFF;
    g_silk = (silk_color[silk_choice]     >>  8) & 0xFF;
    b_silk =  silk_color[silk_choice]            & 0xFF;

    // ── Сохраняем текущую палитру и цвета слоёв ───────────────────────────
    for (i = 0; i < 64; i++)
        saved_pal[i] = palette(i);
    board(B) {
        B.layers(L) saved_col[L.number] = L.color;
    }

    // ── Команды Eagle ──────────────────────────────────────────────────────
    cmd = "";

    // Palette 0  = фон = маска
    // Palette 16 = покрытие падов (tStop)
    // Palette 17 = медь под маской (слои 1, 18, 19)
    // Palette 18 = шелкография (слой 21)
    sprintf(s, "SET PALETTE 0  0x%02X%02X%02X%02X;\n", 0xFF, r_mask, g_mask, b_mask); cmd += s;
    sprintf(s, "SET PALETTE 16 0x%02X%02X%02X%02X;\n", 0xFF, r_fin,  g_fin,  b_fin);  cmd += s;
    sprintf(s, "SET PALETTE 17 0x%02X%02X%02X%02X;\n", 0xFF, r_cu,   g_cu,   b_cu);   cmd += s;
    sprintf(s, "SET PALETTE 18 0x%02X%02X%02X%02X;\n", 0xFF, r_silk, g_silk, b_silk); cmd += s;

    // ── Top ───────────────────────────────────────────────────────────────
    cmd += "SET COLOR_LAYER 29 16;\n";
    cmd += "SET COLOR_LAYER 1  17;\n";
    cmd += "SET COLOR_LAYER 18 17;\n";
    cmd += "SET COLOR_LAYER 19 17;\n";
    cmd += "SET COLOR_LAYER 21 18;\n";

    cmd += "SET Option.LayerSequence 29 21 1 18 19;\n";
    cmd += "DISPLAY NONE;\n";
    cmd += "DISPLAY 1 18 19 20 21 29;\n";

    sprintf(dpi_s, "%d", dpi);
    sprintf(s, "EXPORT IMAGE '%s' %s;\n", tex_dir + "top_texture.png", dpi_s);
    cmd += s;

    // ── Bottom ────────────────────────────────────────────────────────────
    cmd += "SET COLOR_LAYER 30 16;\n";
    cmd += "SET COLOR_LAYER 16 17;\n";
    cmd += "SET COLOR_LAYER 17 17;\n";
    cmd += "SET COLOR_LAYER 18 17;\n";
    cmd += "SET COLOR_LAYER 22 18;\n";

    cmd += "SET Option.LayerSequence 30 22 16 17 18;\n";
    cmd += "DISPLAY NONE;\n";
    cmd += "DISPLAY 16 17 18 20 22 30;\n";

    sprintf(s, "EXPORT IMAGE '%s' %s;\n", tex_dir + "bottom_texture.png", dpi_s);
    cmd += s;

    // ── Восстанавливаем палитру и цвета слоёв ─────────────────────────────
    for (i = 0; i < 64; i++) {
        p  = saved_pal[i];
        aa = (p >> 24) & 0xFF;
        rr = (p >> 16) & 0xFF;
        gg = (p >>  8) & 0xFF;
        bb =  p        & 0xFF;
        sprintf(s, "SET PALETTE %d 0x%02X%02X%02X%02X;\n", i, aa, rr, gg, bb);
        cmd += s;
    }
    board(B) {
        B.layers(L) {
            sprintf(s, "SET COLOR_LAYER %d %d;\n", L.number, saved_col[L.number]);
            cmd += s;
        }
    }
    cmd += "DISPLAY NONE;\n";
    cmd += "DISPLAY 20 17 18 1 21 23 25;\n";

    exit(cmd);
}
