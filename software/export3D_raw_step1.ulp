#usage "NoABS.Eagle3D texture worker (step 1 of 2).\n\
Renders top/bottom board textures via EXPORT IMAGE, then chains step2 (Python).\n\
Settings are read from the board's global NOABS_* attributes (written by export3D.ulp).\n\
Run by eaglecon (Eagle 9 path) or directly in-place (Eagle 7 path):\n\
  RUN export3D_raw_step1.ulp HEADLESS   -- throwaway session: end with SET CONFIRM NO; QUIT\n\
  RUN export3D_raw_step1.ulp INPLACE    -- user's live editor: restore palette, no quit"

string win_path(string s)
{
  string result = s;
  int i;
  for (i = 0; result[i]; i++)
    if (result[i] == '/') result[i] = '\\';
  return result;
}

// Read a global board attribute by name; "" if absent.
string get_attr(string nm)
{
  string r = "";
  board(B) B.attributes(A) if (A.name == nm) r = A.value;
  return r;
}

// Integer attribute with default.
int attr_int(string nm, int def)
{
  string v = get_attr(nm);
  if (strlen(v) == 0) return def;
  return strtol(v);
}

void main()
{
  if (!board) { dlgMessageBox("export3D_raw_step1: no .brd file is open."); exit(1); }

  // ── Mode ──────────────────────────────────────────────────────────────────
  int headless = (argc >= 2 && strupr(argv[1]) == "HEADLESS");

  // ── Board paths ─────────────────────────────────────────────────────────────
  string board_dir, brd_stem, brd_full, tmp_dir, textures_dir;
  board(B)
  {
    board_dir    = filedir(B.name);
    brd_stem     = filesetext(filename(B.name), "");
    brd_full     = B.name;
    tmp_dir      = board_dir + "NoABS_tmp/";
    textures_dir = tmp_dir + brd_stem + "_textures/";
  }
  string scripts_dir = filedir(argv[0]);

  // ── Color presets (must match the dialog in export3D.ulp) ─────────────────────
  string mask_names[], finish_names[], silk_names[];
  int mask_color[], copper_color[], finish_color[], silk_color[];

  mask_names[0] = "Green";   mask_color[0] = 0x1A7C0F; copper_color[0] = 0x298D29;
  mask_names[1] = "Blue";    mask_color[1] = 0x1A18BF; copper_color[1] = 0x2828D8;
  mask_names[2] = "Red";     mask_color[2] = 0x9F180F; copper_color[2] = 0xAE2929;
  mask_names[3] = "Black";   mask_color[3] = 0x1A180F; copper_color[3] = 0x292929;
  mask_names[4] = "Purple";  mask_color[4] = 0x9F1873; copper_color[4] = 0xAE298D;
  mask_names[5] = "White";   mask_color[5] = 0xE2E0D7; copper_color[5] = 0xF1F1F1;

  finish_names[0] = "ENIG (gold)"; finish_color[0] = 0xD4AF37;
  finish_names[1] = "HASL (tin)";  finish_color[1] = 0xC0C0C0;

  silk_names[0] = "White"; silk_color[0] = 0xFEFEFE;
  silk_names[1] = "Black"; silk_color[1] = 0x010101;

  // ── Settings from board attributes (human-readable names → indices) ───────────
  int i;
  int mask_choice = 0, finish_choice = 0, silk_choice = 0;
  string av;
  av = get_attr("NOABS_MASK");   for (i = 0; i < 6; i++) if (mask_names[i]   == av) mask_choice   = i;
  av = get_attr("NOABS_FINISH"); for (i = 0; i < 2; i++) if (finish_names[i] == av) finish_choice = i;
  av = get_attr("NOABS_SILK");   for (i = 0; i < 2; i++) if (silk_names[i]   == av) silk_choice   = i;
  int dpi        = attr_int("NOABS_DPI", 600);
  int photo_vias = attr_int("NOABS_PHOTO_VIAS", 1);
  // Clamp DPI to the dialog's range — a hand-edited attribute bypasses dialog validation.
  if (dpi <= 0)   dpi = 600;    // empty / non-numeric
  if (dpi < 72)   dpi = 72;
  if (dpi > 2400) dpi = 2400;

  // ── Ensure textures dir exists, clear previous textures ───────────────────────
  system("cmd.exe /c mkdir \"" + win_path(textures_dir) + "\" 2>nul"
       + " & del /f /q \"" + win_path(textures_dir) + "top_texture.bmp\" 2>nul"
       + " & del /f /q \"" + win_path(textures_dir) + "bottom_texture.bmp\" 2>nul");

  // Timing probe: Eagle is up and running the worker (step1−launch = Eagle 7 startup).
  int t_now = time();
  output(win_path(tmp_dir + "timing.txt"), "at")
    printf("%d  %02d:%02d:%02d  step1 (eagle ready)\n",
           t_now, t2hour(t_now), t2minute(t_now), t2second(t_now));

  // ── Extract RGB from presets ─────────────────────────────────────────────────
  int r_mask = (mask_color[mask_choice]     >> 16) & 0xFF;
  int g_mask = (mask_color[mask_choice]     >>  8) & 0xFF;
  int b_mask =  mask_color[mask_choice]            & 0xFF;
  int r_cu   = (copper_color[mask_choice]   >> 16) & 0xFF;
  int g_cu   = (copper_color[mask_choice]   >>  8) & 0xFF;
  int b_cu   =  copper_color[mask_choice]          & 0xFF;
  int r_fin  = (finish_color[finish_choice] >> 16) & 0xFF;
  int g_fin  = (finish_color[finish_choice] >>  8) & 0xFF;
  int b_fin  =  finish_color[finish_choice]        & 0xFF;
  int r_silk = (silk_color[silk_choice]     >> 16) & 0xFF;
  int g_silk = (silk_color[silk_choice]     >>  8) & 0xFF;
  int b_silk =  silk_color[silk_choice]            & 0xFF;

  // ── Save current palette / layer state (only needed for in-place restore) ─────
  int saved_pal[], saved_col[], saved_fill[], saved_vis[];
  if (!headless)
  {
    for (i = 0; i < 64; i++)
      saved_pal[i] = palette(i);
    board(B) B.layers(L) {
      saved_col[L.number]  = L.color;
      saved_fill[L.number] = L.fill;
      saved_vis[L.number]  = L.visible;
    }
  }

  // ── Build Eagle command sequence ──────────────────────────────────────────────
  string cmd, s, dpi_str;
  sprintf(dpi_str, "%d", dpi);
  real drill, via_r, via_w, vx, vy;

  cmd  = "ratsnest;\n";
  if (EAGLE_VERSION >= 9)
  {
    cmd += "set Option.SignalNamesOnPads 0;\n";
    cmd += "set Option.SignalNamesOnTraces 0;\n";
  }
  else
  {
    cmd += "set Option.SignalNames = 0;\n";
  }
  cmd += "set Option.ViaLength 0;\n";
  cmd += "set PAD_NAMES OFF;\n";
  cmd += "SET FILL_LAYER 1  1;\n";
  cmd += "SET FILL_LAYER 16 1;\n";
  cmd += "SET FILL_LAYER 17 1;\n";
  cmd += "SET FILL_LAYER 18 1;\n";
  cmd += "SET FILL_LAYER 19 1;\n";
  cmd += "SET FILL_LAYER 20 1;\n";
  cmd += "SET FILL_LAYER 21 1;\n";
  cmd += "SET FILL_LAYER 22 1;\n";
  cmd += "SET FILL_LAYER 29 1;\n";
  cmd += "SET FILL_LAYER 30 1;\n";

  // Palette 0  = background = mask color
  // Palette 16 = pad finish (tStop / bStop)
  // Palette 17 = copper under mask
  // Palette 18 = silkscreen
  // Palette 19 = magenta marker for board outline (layer 20), used by Python to crop
  // Palette 20 = via drill hole (dark), used only when photo_vias=1
  sprintf(s, "SET PALETTE 0  0x%02X%02X%02X%02X;\n", 0xFF, r_mask, g_mask, b_mask); cmd += s;
  sprintf(s, "SET PALETTE 16 0x%02X%02X%02X%02X;\n", 0xFF, r_fin,  g_fin,  b_fin);  cmd += s;
  sprintf(s, "SET PALETTE 17 0x%02X%02X%02X%02X;\n", 0xFF, r_cu,   g_cu,   b_cu);   cmd += s;
  sprintf(s, "SET PALETTE 18 0x%02X%02X%02X%02X;\n", 0xFF, r_silk, g_silk, b_silk); cmd += s;
  cmd += "SET PALETTE 19 0xFFFF00FF;\n";
  cmd += "SET COLOR_LAYER 20 19;\n";

  // ── Photorealistic vias: draw filled circles on layer 200 ─────────────────────
  if (photo_vias)
  {
    cmd += "SET PALETTE 20 0xFF000000;\n";
    cmd += "SET COLOR_LAYER 200 20;\n";
    cmd += "SET FILL_LAYER 200 1;\n";
    board(B) B.signals(S) S.vias(V) {
      drill = u2mm(V.drill);
      via_r = drill / 4.0;
      via_w = drill / 2.0;
      vx    = u2mm(V.x);
      vy    = u2mm(V.y);
      cmd += "LAYER 200;\n";
      sprintf(s, "CHANGE WIDTH %.4fmm;\n", via_w); cmd += s;
      sprintf(s, "CIRCLE (%.4fmm %.4fmm) (%.4fmm %.4fmm);\n", vx, vy, vx + via_r, vy); cmd += s;
    }
  }

  // ── LayerSequence — set BEFORE any DISPLAY ───────────────────────────────────
  cmd += "SET Option.LayerSequence 200t 20t 29t 21t 18 17 1-16 22b 30b 20b 200b;\n";

  // ── Top texture ───────────────────────────────────────────────────────────────
  cmd += "SET COLOR_LAYER 29 16;\n";
  cmd += "SET COLOR_LAYER 1  17;\n";
  cmd += "SET COLOR_LAYER 17 17;\n";
  cmd += "SET COLOR_LAYER 18 17;\n";
  cmd += "SET COLOR_LAYER 21 18;\n";
  cmd += "DISPLAY NONE;\n";
  if (photo_vias)
    cmd += "DISPLAY 20 21 29 1 17 18 200;\n";
  else
    cmd += "DISPLAY 20 21 29 1 17 18;\n";
  sprintf(s, "EXPORT IMAGE '%s' %s;\n", textures_dir + "top_texture.bmp", dpi_str); cmd += s;

  // ── Bottom texture ────────────────────────────────────────────────────────────
  cmd += "SET COLOR_LAYER 30 16;\n";
  cmd += "SET COLOR_LAYER 16 17;\n";
  cmd += "SET COLOR_LAYER 17 17;\n";
  cmd += "SET COLOR_LAYER 18 17;\n";
  cmd += "SET COLOR_LAYER 22 18;\n";
  cmd += "DISPLAY NONE;\n";
  if (photo_vias)
    cmd += "DISPLAY 16 17 18 20 22 30 200;\n";
  else
    cmd += "DISPLAY 16 17 18 20 22 30;\n";
  sprintf(s, "EXPORT IMAGE '%s' %s;\n", textures_dir + "bottom_texture.bmp", dpi_str); cmd += s;

  // ── In-place: clean up via circles and restore palette / layer state ──────────
  if (!headless)
  {
    if (photo_vias)
    {
      cmd += "DISPLAY NONE;\n";
      cmd += "DISPLAY 200;\n";
      cmd += "GROUP ALL;\n";
      cmd += "DELETE (>0 0);\n";
    }

    int p, aa, rr, gg, bb;
    for (i = 0; i < 64; i++) {
      p  = saved_pal[i];
      aa = (p >> 24) & 0xFF;
      rr = (p >> 16) & 0xFF;
      gg = (p >>  8) & 0xFF;
      bb =  p        & 0xFF;
      sprintf(s, "SET PALETTE %d 0x%02X%02X%02X%02X;\n", i, aa, rr, gg, bb); cmd += s;
    }
    board(B) B.layers(L) {
      sprintf(s, "SET COLOR_LAYER %d %d;\n", L.number, saved_col[L.number]);  cmd += s;
      sprintf(s, "SET FILL_LAYER %d %d;\n",  L.number, saved_fill[L.number]); cmd += s;
    }

    cmd += "DISPLAY NONE;\n";
    if (EAGLE_VERSION >= 9)
    {
      cmd += "set Option.SignalNamesOnPads 1;\n";
      cmd += "set Option.SignalNamesOnTraces 1;\n";
    }
    else
    {
      cmd += "set Option.SignalNames = 1;\n";
    }
    cmd += "set PAD_NAMES ON;\n";
    string disp; int li;
    disp = "DISPLAY";
    for (li = 1; li <= 255; li++)
      if (saved_vis[li]) { sprintf(s, " %d", li); disp += s; }
    disp += ";\n";
    cmd += disp;

    // Save board to disk so Python (step2) reads the current geometry.
    cmd += "WRITE;\n";
  }

  // ── Chain step2 (Python) ──────────────────────────────────────────────────────
  string step2_path = scripts_dir;
  int slen = strlen(step2_path);
  if (slen > 0 && step2_path[slen-1] != '/' && step2_path[slen-1] != '\\')
    step2_path += "/";
  int ci;
  for (ci = 0; step2_path[ci]; ci++)
    if (step2_path[ci] == '\\') step2_path[ci] = '/';
  step2_path += "export3D_raw_step2.ulp";
  cmd += "RUN '" + step2_path + "';\n";

  // NOTE: in HEADLESS mode the caller must terminate the eaglecon session at the
  // top level of its -C string, e.g.  -C "RUN export3D_raw_step1.ulp HEADLESS; SET CONFIRM NO; QUIT".
  // QUIT issued from inside this returned command string is rejected by EAGLE
  // ("cannot close window while a command is running"). In INPLACE mode the board
  // was already saved (WRITE above) and the user's editor stays open.

  exit(cmd);
}
